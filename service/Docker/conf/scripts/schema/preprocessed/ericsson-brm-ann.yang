module ericsson-brm-ann {
  yang-version 1.1;
  namespace "urn:rdns:com:ericsson:oammodel:ericsson-brm-ann";
  prefix brme-ann;

  import ericsson-yang-types {
    prefix typese;
  }
  import ericsson-notifications {
    prefix notife;
  }
  import ietf-yang-types {
    prefix yang;
  }
  import ietf-inet-types {
    prefix inet;
  }
  import ietf-netconf-acm {
    prefix nacm;
  }
  import ericsson-ftp-client {
    prefix ftpclie;
  }
  import tailf-common {
    prefix tailf;
  }
  import ericsson-yang-extensions {
    prefix yexte;
  }

  organization
    "Ericsson AB";
  contact
    "Ericsson first line support via email";
  description
    "Backup Restore Management root

     Copyright Ericsson AB [2019-2022]. All rights reserved.";

  revision 2022-09-02 {
    description
      "Generated by eyang-annotator 1.29.0-60 2024-02-08 17:10:07 CET on 2024-02-12 17:08:55.";
    yexte:version "4";
    yexte:release "5";
    yexte:correction "0";
  }
  tailf:annotate-module ericsson-brm {
    tailf:annotate-statement "container[name='brm']" {
      tailf:annotate-statement "list[name='backup-manager']" {
        tailf:annotate-statement "leaf[name='auto-export']" {
          tailf:meta-data yexte:privacy-event;
        }
      }
    }
    tailf:annotate-statement "container[name='brm']" {
      tailf:annotate-statement "list[name='backup-manager']" {
        tailf:annotate-statement "choice[name='sftp-server-connection']" {
          tailf:annotate-statement "case[name='password']" {
            tailf:annotate-statement "leaf[name='auto-export-uri']" {
              tailf:meta-data yexte:privacy-event;
            }
          }
        }
      }
    }
    tailf:annotate-statement "container[name='brm']" {
      tailf:annotate-statement "list[name='backup-manager']" {
        tailf:annotate-statement "choice[name='sftp-server-connection']" {
          tailf:annotate-statement "case[name='password']" {
            tailf:annotate-statement "leaf[name='auto-export-password']" {
              tailf:meta-data yexte:is-passphrase;
            }
          }
        }
      }
    }
    tailf:annotate-statement "container[name='brm']" {
      tailf:annotate-statement "list[name='backup-manager']" {
        tailf:annotate-statement "choice[name='sftp-server-connection']" {
          tailf:annotate-statement "case[name='password']" {
            tailf:annotate-statement "leaf[name='auto-export-password']" {
              tailf:meta-data yexte:privacy-event;
            }
          }
        }
      }
    }
    tailf:annotate-statement "container[name='brm']" {
      tailf:annotate-statement "list[name='backup-manager']" {
        tailf:annotate-statement "choice[name='sftp-server-connection']" {
          tailf:annotate-statement "case[name='password']" {
            tailf:annotate-statement "leaf[name='auto-export-password']" {
              tailf:suppress-echo true;
            }
          }
        }
      }
    }
    tailf:annotate-statement "container[name='brm']" {
      tailf:annotate-statement "list[name='backup-manager']" {
        tailf:annotate-statement "action[name='create-backup']" {
          tailf:actionpoint cpa-action;
        }
      }
    }
    tailf:annotate-statement "container[name='brm']" {
      tailf:annotate-statement "list[name='backup-manager']" {
        tailf:annotate-statement "action[name='delete-backup']" {
          tailf:actionpoint cpa-action;
        }
      }
    }
    tailf:annotate-statement "container[name='brm']" {
      tailf:annotate-statement "list[name='backup-manager']" {
        tailf:annotate-statement "action[name='cancel-current-action']" {
          tailf:actionpoint cpa-action;
        }
      }
    }
    tailf:annotate-statement "container[name='brm']" {
      tailf:annotate-statement "list[name='backup-manager']" {
        tailf:annotate-statement "action[name='import-backup']" {
          tailf:annotate-statement "input" {
            tailf:annotate-statement "choice[name='sftp-server-connection']" {
              tailf:annotate-statement "case[name='password']" {
                tailf:annotate-statement "leaf[name='password']" {
                  tailf:meta-data yexte:is-passphrase;
                }
              }
            }
          }
        }
      }
    }
    tailf:annotate-statement "container[name='brm']" {
      tailf:annotate-statement "list[name='backup-manager']" {
        tailf:annotate-statement "action[name='import-backup']" {
          tailf:annotate-statement "input" {
            tailf:annotate-statement "choice[name='sftp-server-connection']" {
              tailf:annotate-statement "case[name='password']" {
                tailf:annotate-statement "leaf[name='password']" {
                  tailf:suppress-echo true;
                }
              }
            }
          }
        }
      }
    }
    tailf:annotate-statement "container[name='brm']" {
      tailf:annotate-statement "list[name='backup-manager']" {
        tailf:annotate-statement "action[name='import-backup']" {
          tailf:annotate-statement "output" {
            tailf:annotate-statement "leaf[name='return-value']" {
              tailf:meta-data yexte:privacy-event;
            }
          }
        }
      }
    }
    tailf:annotate-statement "container[name='brm']" {
      tailf:annotate-statement "list[name='backup-manager']" {
        tailf:annotate-statement "action[name='import-backup']" {
          tailf:actionpoint cpa-action;
        }
      }
    }
    tailf:annotate-statement "container[name='brm']" {
      tailf:annotate-statement "list[name='backup-manager']" {
        tailf:annotate-statement "list[name='backup']" {
          tailf:annotate-statement "action[name='restore']" {
            tailf:actionpoint cpa-action;
          }
        }
      }
    }
    tailf:annotate-statement "container[name='brm']" {
      tailf:annotate-statement "list[name='backup-manager']" {
        tailf:annotate-statement "list[name='backup']" {
          tailf:annotate-statement "action[name='cancel-current-action']" {
            tailf:actionpoint cpa-action;
          }
        }
      }
    }
    tailf:annotate-statement "container[name='brm']" {
      tailf:annotate-statement "list[name='backup-manager']" {
        tailf:annotate-statement "list[name='backup']" {
          tailf:annotate-statement "action[name='export']" {
            tailf:annotate-statement "input" {
              tailf:annotate-statement "choice[name='sftp-server-connection']" {
                tailf:annotate-statement "case[name='password']" {
                  tailf:annotate-statement "leaf[name='password']" {
                    tailf:meta-data yexte:is-passphrase;
                  }
                }
              }
            }
          }
        }
      }
    }
    tailf:annotate-statement "container[name='brm']" {
      tailf:annotate-statement "list[name='backup-manager']" {
        tailf:annotate-statement "list[name='backup']" {
          tailf:annotate-statement "action[name='export']" {
            tailf:annotate-statement "input" {
              tailf:annotate-statement "choice[name='sftp-server-connection']" {
                tailf:annotate-statement "case[name='password']" {
                  tailf:annotate-statement "leaf[name='password']" {
                    tailf:suppress-echo true;
                  }
                }
              }
            }
          }
        }
      }
    }
    tailf:annotate-statement "container[name='brm']" {
      tailf:annotate-statement "list[name='backup-manager']" {
        tailf:annotate-statement "list[name='backup']" {
          tailf:annotate-statement "action[name='export']" {
            tailf:annotate-statement "output" {
              tailf:annotate-statement "leaf[name='return-value']" {
                tailf:meta-data yexte:privacy-event;
              }
            }
          }
        }
      }
    }
    tailf:annotate-statement "container[name='brm']" {
      tailf:annotate-statement "list[name='backup-manager']" {
        tailf:annotate-statement "list[name='backup']" {
          tailf:annotate-statement "action[name='export']" {
            tailf:actionpoint cpa-action;
          }
        }
      }
    }
    tailf:annotate-statement "container[name='brm']" {
      tailf:annotate-statement "list[name='backup-manager']" {
        tailf:annotate-statement "container[name='housekeeping']" {
          tailf:annotate-statement "leaf[name='auto-delete']" {
            tailf:meta-data yexte:privacy-event;
          }
        }
      }
    }
    tailf:annotate-statement "container[name='brm']" {
      tailf:annotate-statement "list[name='backup-manager']" {
        tailf:annotate-statement "container[name='scheduler']" {
          tailf:annotate-statement "leaf[name='auto-export']" {
            tailf:meta-data yexte:privacy-event;
          }
        }
      }
    }
    tailf:annotate-statement "container[name='brm']" {
      tailf:annotate-statement "list[name='backup-manager']" {
        tailf:annotate-statement "container[name='scheduler']" {
          tailf:annotate-statement "choice[name='sftp-server-connection']" {
            tailf:annotate-statement "case[name='password']" {
              tailf:annotate-statement "leaf[name='auto-export-uri']" {
                tailf:meta-data yexte:privacy-event;
              }
            }
          }
        }
      }
    }
    tailf:annotate-statement "container[name='brm']" {
      tailf:annotate-statement "list[name='backup-manager']" {
        tailf:annotate-statement "container[name='scheduler']" {
          tailf:annotate-statement "choice[name='sftp-server-connection']" {
            tailf:annotate-statement "case[name='password']" {
              tailf:annotate-statement "leaf[name='auto-export-password']" {
                tailf:meta-data yexte:is-passphrase;
              }
            }
          }
        }
      }
    }
    tailf:annotate-statement "container[name='brm']" {
      tailf:annotate-statement "list[name='backup-manager']" {
        tailf:annotate-statement "container[name='scheduler']" {
          tailf:annotate-statement "choice[name='sftp-server-connection']" {
            tailf:annotate-statement "case[name='password']" {
              tailf:annotate-statement "leaf[name='auto-export-password']" {
                tailf:meta-data yexte:privacy-event;
              }
            }
          }
        }
      }
    }
    tailf:annotate-statement "container[name='brm']" {
      tailf:annotate-statement "list[name='backup-manager']" {
        tailf:annotate-statement "container[name='scheduler']" {
          tailf:annotate-statement "choice[name='sftp-server-connection']" {
            tailf:annotate-statement "case[name='password']" {
              tailf:annotate-statement "leaf[name='auto-export-password']" {
                tailf:suppress-echo true;
              }
            }
          }
        }
      }
    }
    tailf:annotate-statement "container[name='brm']" {
      tailf:annotate-statement "list[name='backup-manager']" {
        tailf:annotate-statement "container[name='failsafe-backup']" {
          tailf:annotate-statement "leaf[name='time-remaining']" {
            tailf:meta-data notife:notifiable-state-data {
              tailf:meta-value false;
            }
          }
        }
      }
    }
    tailf:annotate-statement "container[name='brm']" {
      tailf:annotate-statement "list[name='backup-manager']" {
        tailf:annotate-statement "container[name='failsafe-backup']" {
          tailf:annotate-statement "action[name='deactivate']" {
            tailf:actionpoint cpa-action;
          }
        }
      }
    }
    tailf:annotate-statement "container[name='brm']" {
      tailf:annotate-statement "list[name='backup-manager']" {
        tailf:annotate-statement "container[name='failsafe-backup']" {
          tailf:annotate-statement "action[name='activate']" {
            tailf:actionpoint cpa-action;
          }
        }
      }
    }
    tailf:annotate-statement "container[name='brm']" {
      tailf:annotate-statement "list[name='backup-manager']" {
        tailf:meta-data yexte:is-system-created;
      }
    }
    tailf:annotate-statement "container[name='brm']" {
      tailf:annotate-statement "container[name='rollback-at-restore']" {
        tailf:annotate-statement "action[name='confirm-restore']" {
          tailf:actionpoint cpa-action;
        }
      }
    }
    tailf:annotate-statement "container[name='brm']" {
      tailf:callpoint cpa;
    }
    tailf:annotate-statement "container[name='brm']" {
      tailf:meta-data notife:notifiable-state-data {
        tailf:meta-value true;
      }
    }
  }
}
