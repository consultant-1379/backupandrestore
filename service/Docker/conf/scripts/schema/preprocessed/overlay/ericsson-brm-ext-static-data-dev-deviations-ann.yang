module ericsson-brm-ext-static-data-dev-deviations-ann {
  yang-version 1.1;
  namespace "urn:rdns:com:ericsson:oammodel:ericsson-brm-ext-static-data-dev-deviations-ann";
  prefix brmxesddedeviations-ann;

  import ericsson-brm {
    prefix brme;
  }
  import tailf-common {
    prefix tailf;
  }
  import ericsson-yang-extensions {
    prefix yexte;
  }

  organization
    "Ericsson AB";
  contact
    "Ericsson first line support via email";
  description
    "Annotations on deviate statements from ericsson-brm-ext-static-data-dev@2024-01-23
         Copyright Ericsson AB 2024. All rights reserved.";

  revision 2024-02-13 {
    description
      "Generated by eyang-annotator 1.29.0-61 2024-02-12 18:26:56 CET on 2024-02-13 18:07:04.";
    yexte:version "1";
    yexte:release "0";
    yexte:correction "0";
  }
  tailf:annotate /brme:brm/brme:backup-manager/brme:failsafe-backup/brme:backup-name {
    tailf:meta-data yexte:static-data {
      tailf:meta-value true;
    }
  }
  tailf:annotate /brme:brm/brme:backup-manager/brme:backup-type {
    tailf:meta-data yexte:static-data {
      tailf:meta-value true;
    }
  }
  tailf:annotate /brme:brm/brme:backup-manager/brme:failsafe-backup/brme:progress-report {
    tailf:meta-data yexte:static-data {
      tailf:meta-value true;
    }
  }
  tailf:annotate /brme:brm/brme:backup-manager/brme:label-store {
    tailf:meta-data yexte:static-data {
      tailf:meta-value true;
    }
  }
  tailf:annotate /brme:brm/brme:backup-manager/brme:backup {
    tailf:meta-data yexte:static-data {
      tailf:meta-value true;
    }
  }
  tailf:annotate /brme:brm/brme:backup-manager/brme:progress-report {
    tailf:meta-data yexte:static-data {
      tailf:meta-value true;
    }
  }
  tailf:annotate /brme:brm/brme:backup-manager/brme:failsafe-backup/brme:time-remaining {
    tailf:meta-data yexte:static-data {
      tailf:meta-value true;
    }
  }
  tailf:annotate /brme:brm/brme:backup-manager/brme:scheduler/brme:most-recently-created-auto-backup {
    tailf:meta-data yexte:static-data {
      tailf:meta-value true;
    }
  }
  tailf:annotate /brme:brm/brme:backup-manager/brme:scheduler/brme:progress-report {
    tailf:meta-data yexte:static-data {
      tailf:meta-value true;
    }
  }
  tailf:annotate /brme:brm/brme:backup-manager/brme:failsafe-backup/brme:usage-state {
    tailf:meta-data yexte:static-data {
      tailf:meta-value true;
    }
  }
  tailf:annotate /brme:brm/brme:backup-manager/brme:scheduler/brme:next-scheduled-time {
    tailf:meta-data yexte:static-data {
      tailf:meta-value true;
    }
  }
  tailf:annotate /brme:brm/brme:backup-manager/brme:backup-domain {
    tailf:meta-data yexte:static-data {
      tailf:meta-value true;
    }
  }
  tailf:annotate /brme:brm/brme:rollback-at-restore/brme:time-remaining-before-rollback {
    tailf:meta-data yexte:static-data {
      tailf:meta-value true;
    }
  }
}
